(defun c:TLEN (/ ss i obj len total)
  (vl-load-com)
  (setq total 0.0)
  (prompt "\nВыберите линии, полилинии или дуги: ")
  (if (setq ss (ssget '((0 . "LINE,*POLYLINE,ARC,SPLINE"))))
    (progn
      (setq i 0)
      (while (< i (sslength ss))
        (setq obj (vlax-ename->vla-object (ssname ss i)))
        (setq len (vlax-curve-getDistAtParam obj (vlax-curve-getEndParam obj)))
        (setq total (+ total len))
        (setq i (1+ i))
      )
      (alert (strcat "Общая длина: " (rtos total 2 3)))
      (princ (strcat "\nОбщая длина: " (rtos total 2 3)))
    )
    (princ "\nОбъекты не выбраны.")
  )
  (princ)
)
